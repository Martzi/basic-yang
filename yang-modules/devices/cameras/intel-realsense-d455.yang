module intel-realsense-d455 {
  namespace "urn:ietf:params:xml:ns:yang:intel-realsense-d455";
  prefix "d455";

  import usb-interface {
    prefix "usb";
  }
  import usb3-interface {
    prefix "usb3";
  }

  description
    "This module defines the Intel RealSense D455 camera with relevant parameters and a single USB interface.";

  revision "2024-09-09" {
    description "Initial revision for Intel RealSense D455 camera.";

  container camera {
    description "Intel RealSense D455 depth camera configuration";

    leaf model {
      type string;
      default "RealSense D455";
      description "Model name of the camera.";
    }

    leaf manufacturer {
      type string;
      default "Intel";
      description "Manufacturer of the camera.";
    }

    container rgb-camera {
      description "RGB camera configuration";

      leaf resolution {
        type string {
          pattern "[0-9]+x[0-9]+";  // Example: "1920x1080"
        }
        default "1920x1080";
        description "RGB resolution of the camera in width x height format.";
      }

      leaf frame-rate {
        type uint16;
        units "fps";
        default "30";
        description "Frame rate of the RGB camera in frames per second.";
      }
    }

    container depth-camera {
      description "Depth camera configuration";

      leaf depth-resolution {
        type string {
          pattern "[0-9]+x[0-9]+";  // Example: "1280x720"
        }
        default "1280x720";
        description "Depth resolution of the camera in width x height format.";
      }

      leaf depth-frame-rate {
        type uint16;
        units "fps";
        default "90";
        description "Frame rate of the depth camera in frames per second.";
      }

      leaf max-range {
        type decimal64 {
          fraction-digits 2;
        }
        units "meters";
        default "10.00";
        description "Maximum range of the depth camera in meters.";
      }
    }

    leaf field-of-view {
      type uint16;
      units "degrees";
      default "90";
      description "Field of view of the camera in degrees.";
    }

    leaf power-consumption {
      type decimal64 {
        fraction-digits 2;
      }
      units "W";
      default "3.5";  // Typical power consumption for the Intel RealSense D455
      description "Power consumption of the camera in watts.";
    }

    container usb-interface {
      description "USB interface of the camera";

      leaf interface-id {
        type string;
        default "usb3-port1";
        description "Unique identifier for the USB interface.";
      }

      uses usb:usb-interface;  // Reuse the usb-interface grouping for USB attributes

      augment "/usb:usb-interface" {
        when "usb:version = 'USB3.0'";
        description "USB3.0-specific attributes";
        
        leaf usb3-max-current {
          type uint16;
          units "mA";
          default "900";  // Max current for USB3.0 interface
          description "Maximum current for the USB3.0 interface.";
        }

        leaf usb3-signaling-rate {
          type decimal64 {
            fraction-digits 2;
          }
          units "Gbps";
          default "5.00";  // USB 3.0 signaling rate
          description "Signaling rate for USB3.0.";
        }

        leaf backward-compatible {
          type boolean;
          default "true";
          description "Indicates if the USB3.0 interface is backward compatible with USB2.0.";
        }
      }
    }
  }
}
