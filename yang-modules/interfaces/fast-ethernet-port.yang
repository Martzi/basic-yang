module fast-ethernet-port {
  namespace "urn:ietf:params:xml:ns:yang:fast-ethernet-port";
  prefix "fe";

  import ietf-network {
    prefix "nw";
  }

  import ietf-network-topology {
    prefix "nt";
  }

  import device-layer {
    prefix "dl";
  }

  import ethernet-port {
    prefix "eth";
  }

  description
    "This module augments the generic Ethernet port with Fast Ethernet (100BASE-T) specific parameters.";

  revision "2024-09-09" {
    description "Initial revision.";
  }

  // augment "/eth:ethernet-port" {
  augment "/nw:networks/nw:network/nw:node/nt:termination-point/dl:device-layer-termination-point-attributes/eth:ethernet-port" {
    when "eth:speed = '100Mbps'";
    description "Fast Ethernet (100BASE-T) specific attributes";

    leaf max-frame-size {
      type uint16;
      default "1518";  // Default maximum frame size in bytes
      description "Maximum Ethernet frame size for Fast Ethernet.";
    }

    leaf autonegotiation {
      type boolean;
      default "true";  // Default to autonegotiation enabled
      description "Indicates if autonegotiation is enabled.";
    }
  }
}
