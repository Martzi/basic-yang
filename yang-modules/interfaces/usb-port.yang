module usb-port {
  namespace "urn:ietf:params:xml:ns:yang:usb-port";
  prefix "usb";

  import ietf-network {
    prefix "nw";
  }

  import ietf-network-topology {
    prefix "nt";
  }

  import device-layer {
    prefix "dl";
  }

  description
    "This module defines a generic USB port with default values.";

  revision "2024-09-09" {
    description "Initial revision.";
  }

  augment "/nw:networks/nw:network/nw:node/nt:termination-point/dl:device-layer-termination-point-attributes"{
    when "/nw:networks/nw:network/nw:network-types/dl:device-layer-topology" {
    }
    container usb-port {
      description "Generic USB port";

      leaf port-id {
        type string;
        description "Unique identifier for the USB port.";
      }

      leaf version {
        type string;
        description "Version of the USB port (e.g., USB2.0, USB3.0).";
      }

      leaf speed {
        type decimal64 {
          fraction-digits 2;
        }
        default "0.48";  // Default speed for USB2.0 in Gbps
        description "Maximum speed of the port in Gbps.";
      }

      leaf power-consumption {
        type decimal64 {
          fraction-digits 2;
        }
        units "W";
        default "2.5";  // Default power consumption for USB2.0 in watts
        description "Power consumption of the port.";
      }
    }
  }
}
