module usb2-port {
  namespace "urn:ietf:params:xml:ns:yang:usb2-port";
  prefix "usb2";

  import usb-port {
    prefix "usb";
  }

  description
    "This module augments the generic USB port with USB2.0-specific parameters.";

  revision "2024-09-09" {
    description "Initial revision.";
  }

  augment "/usb:usb-port" {
    when "usb:version = 'USB2.0'";
    description "USB2.0-specific attributes";

    leaf max-current {
      type uint16;
      units "mA";
      default "500";  // Default max current for USB2.0 in mA
      description "Maximum current for USB2.0 port.";
    }

    leaf signaling-rate {
      type decimal64 {
        fraction-digits 2;
      }
      units "Mbps";
      default "480";  // Default signaling rate for USB2.0 in Mbps
      description "Signaling rate of USB2.0.";
    }
  }
}
