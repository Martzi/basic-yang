module gigabit-ethernet-port {
  namespace "urn:ietf:params:xml:ns:yang:gigabit-ethernet-port";
  prefix "ge";

  import ietf-network {
    prefix "nw";
  }

  import ietf-network-topology {
    prefix "nt";
  }

  import device-layer {
    prefix "dl";
  }

  import ethernet-port {
    prefix "eth";
  }

  description
    "This module augments the generic Ethernet port with Gigabit Ethernet (1000BASE-T) specific parameters.";

  revision "2024-09-09" {
    description "Initial revision.";
  }

  augment "/nw:networks/nw:network/nw:node/nt:termination-point/dl:device-layer-termination-point-attributes/eth:ethernet-port" {
    when "eth:speed = '1Gbps'";
    description "Gigabit Ethernet (1000BASE-T) specific attributes";

    leaf max-frame-size {
      type uint16;
      default "1518";  // Default maximum frame size in bytes
      description "Maximum Ethernet frame size for Gigabit Ethernet.";
    }

    leaf autonegotiation {
      type boolean;
      default "true";  // Default to autonegotiation enabled
      description "Indicates if autonegotiation is enabled.";
    }

    leaf energy-efficient-ethernet {
      type boolean;
      default "true";  // Default to Energy Efficient Ethernet enabled
      description "Indicates if Energy Efficient Ethernet (EEE) is supported.";
    }
  }
}
