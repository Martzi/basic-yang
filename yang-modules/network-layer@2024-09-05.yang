module network-layer {
    yang-version 1.1;
    namespace "urn:ietf:params:xml:ns:yang:network-layer";
    prefix nl;
    
    import ietf-network {
        prefix nw;
    }

    import ietf-inet-types {
        prefix inet;
        reference
          "RFC 6991: Common YANG Data Types";
    }

    import ietf-network-topology {
        prefix nt;
    }
    
    organization
      "HSN-Lab & Ericsson Research Hungary";

    contact
      "Editor:    Attila Vidacs
       <mailto:vidacs.attila@vik.bme.hu>
       
       Editor:     Marcell Balogh
       <mailto:balogh.marcell@edu.bme.hu>";

    description
      "This module defines a model for network-layer attributes.";

    revision 2024-09-05 {
        description
          "remove hardcoded elements,
          added as augmentation targets";
        reference
          "A YANG Data Model for Device layer in
           Robot Network Topologies";
    }   

    revision 2024-07-24 {
        description
          "enums updated, aligned with attibute docs";
        reference
          "A YANG Data Model for Device layer in
           Robot Network Topologies";
    } 

    revision 2024-06-13 {
        description
          "Initial revision";
        reference
          "A YANG Data Model for Network layer in
           Robot Network Topologies";
    }

    grouping network-layer-network-type {
        description
            "Indicates the topology type to be L2.";
        container network-layer-topology {
            presence "Indicates L2 Network Topology.";
            description
            "The presence of the container node indicates
            L2 Network Topology.";
        }
    }

    grouping network-layer-node-attributes {
        description
            "L2 node attributes.";
        container network-layer-node-attributes {
            description
              "Contains network layer node attributes";
            leaf node-name {
                type string;
                description
                  "Name of the network layer node.";
            }
            leaf node-type {
                type enumeration{
                    enum generic;
                }
                description
                  "Type of network layer node.";
            }
        }
    }


    grouping network-layer-termination-point-attributes {
        description
            "L2 termination point attributes.";
        container network-layer-termination-point-attributes {
            description
              "Contains termination point network-layer attributes";
            leaf interface-name {
                type string;
                description
                  "Name of the network layer interface.";
            }
            container interface-type{

            // leaf interface-type {
            //     type enumeration{
            //         enum wireless;
            //         enum ethernet;
            //         enum ip;
            //         enum usb;
            //         enum ue-csi;
            //         enum upf-csi;
            //         enum serial;
            //         enum generic;
            //     }
                description
                  "Serves as an augmentation target.";
            }
            leaf interface-status {
                type enumeration{
                    enum up;
                    enum down;
                }
                description
                  "Describes wether the interface is enabled or disabled.";
            }
            leaf ip-address{
                type inet:ip-address;
                when "../interface-type = 'ip'"{}
                description
                  "IP address of the interface.";
            }
            leaf mac-address{
                type string;
                when "../interface-type = 'ethernet'"{}
                description
                  "MAC address of the interface device.";
            }
        }
    }

    grouping network-layer-link-attributes {
        description
            "L2 link attributes.";
        container network-layer-link-attributes {
            description
                "Contains network layer link attributes";
            leaf link-name {
                type string;
                description
                    "Name of the network layer link.";
            }
            leaf link-type {
                type enumeration{
                    enum ethernet;
                    enum ip;
                    enum 3gpp-5g-pdu-session;
                    enum 3gpp-5g-qos-flow;
                    enum tcp;
                    enum udp;
                    enum qos-flow;
                    enum pdu-session;
                    enum generic;
                }
                description
                    "Type of network layer link.";
            }
            leaf _5qi {
                type uint8;
                when "../link-type='3gpp-5g-qos-flow'"{}
            }
            leaf gfbr {
                type uint8;
                when "../link-type='3gpp-5g-qos-flow'"{}
            }
            leaf mfbr {
                type uint8;
                when "../link-type='3gpp-5g-qos-flow'"{}
            }
            leaf pdb {
                type uint8;
                when "../link-type='3gpp-5g-qos-flow'"{}
            }
            leaf per {
                type uint8;
                when "../link-type='3gpp-5g-qos-flow'"{}
            }
        }
    }


    // augment "/nw:networks/nw:network/nw:network-types" {
    //     description
    //         "Introduces new network type for L2 topology.";
    //     uses l2-network-type;
    // }

    // augment "/nw:networks/nw:network" {
    //     when '/nw:networks/nw:network/nw:network-types/nw:network-layer-topology' {
    //         description
    //             "Augmentation parameters apply only for networks
    //             with L2 topology.";
    //     }
    //     description
    //         "Configuration parameters for the L2 network
    //         as a whole.";
    //     uses network-layer-topology-attributes;
    // }

    augment "/nw:networks/nw:network/nw:node" {
        when '/nw:networks/nw:network/nw:network-types/nw:network-layer-topology' {
            description
                "Augmentation parameters apply only for networks
                with L2 topology.";
        }
        description
            "Configuration parameters for L2 at the node
            level.";
        uses network-layer-node-attributes;
    }

    augment "/nw:networks/nw:network/nt:link" {
        when '/nw:networks/nw:network/nw:network-types/nw:network-layer-topology' {
            description
                "Augmentation parameters apply only for networks
                with L2 topology.";
        }
        description
            "Augments L2 topology link information.";
        uses network-layer-link-attributes;
    }

    augment "/nw:networks/nw:network/nw:node/nt:termination-point" {
        when '/nw:networks/nw:network/nw:network-types/nw:network-layer-topology' {
            description
                "Augmentation parameters apply only for networks
                with L2 topology.";
        }
        description
            "Augments L2 topology termination point information.";
        uses network-layer-termination-point-attributes;
    }

}
