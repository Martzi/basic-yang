module network-layer {
    yang-version 1.1;
    namespace "urn:ietf:params:xml:ns:yang:network-layer";
    prefix nl;
    
    import ietf-network {
        prefix nw;
    }

    import ietf-inet-types {
        prefix inet;
        reference
          "RFC 6991: Common YANG Data Types";
    }

    import ietf-network-topology {
        prefix nt;
    }
    
    organization
      "HSN-Lab & Ericsson Research Hungary";

    contact
      "Editor:    Attila Vidacs
       <mailto:vidacs.attila@vik.bme.hu>
       
       Editor:     Marcell Balogh
       <mailto:balogh.marcell@edu.bme.hu>";

    description
      "This module defines a model for network-layer attributes.";

    revision 2024-09-10 {
        description
          "hardcoded components outsorced,
          added as augmentation target";
        reference
          "A YANG Data Model for Device layer in
           Robot Network Topologies";
    }
    
    revision 2024-07-24 {
        description
          "enums updated, aligned with attibute docs";
        reference
          "A YANG Data Model for Device layer in
           Robot Network Topologies";
    }

    revision 2024-06-13 {
        description
          "Initial revision";
        reference
          "A YANG Data Model for Network layer in
           Robot Network Topologies";
    }

    augment "/nw:networks/nw:network/nw:network-types" {
        description
            "Network-layer augmentation with a presence attribute.";
        container network-layer-topology {
            presence "indicates network-layer topology.";
            description
                "The presence of the container node indicates
                network-layer topology.";
        }
    }

    augment "/nw:networks/nw:network/nw:node" {
        // when "../nl:network-layer-topology" {
        when "/nw:networks/nw:network/nw:network-types/nl:network-layer-topology" {
        }
        description
          "Augmentation parameters apply only for networks with
           network-layer topology";
        container network-layer-node-attributes {
            description
              "Contains network layer node attributes";
            leaf node-name {
                type string;
                description
                  "Name of the network layer node.";
            }
            leaf node-type {
                type enumeration{
                    enum generic;
                }
                description
                  "Type of network layer node.";
            }
        }
    }

    augment "/nw:networks/nw:network/nw:node/"
         +"nt:termination-point" {
        // when "../../nl:network-layer-topology" {
        when "/nw:networks/nw:network/nw:network-types/nl:network-layer-topology" {
        }
        description
          "Augmentation parameters apply only for networks with
           network-layer topology";
        container network-layer-termination-point-attributes {
            description
              "Contains termination point network-layer attributes";
            leaf interface-name {
                type string;
                description
                  "Name of the network layer interface.";
            }
            leaf interface-type {
                type enumeration{
                    enum wireless;
                    enum ethernet;
                    enum ip;
                    enum usb;
                    enum ue-csi;
                    enum upf-csi;
                    enum serial;
                    enum generic;
                }
                description
                  "Type of the interface. (E.g., Gigabit Ethernet, USB 3.1 Gen 2)";
            }
            leaf interface-status {
                type enumeration{
                    enum up;
                    enum down;
                }
                description
                  "Describes wether the interface is enabled or disabled.";
            }
            leaf ip-address{
                type inet:ip-address;
                when "../interface-type = 'ip'"{}
                description
                  "IP address of the interface.";
            }
            leaf mac-address{
                type string;
                when "../interface-type = 'ethernet'"{}
                description
                  "MAC address of the interface device.";
            }
        }
    }

    augment "/nw:networks/nw:network/nt:link" {
        // when "../nl:network-layer-topology" {
        when "/nw:networks/nw:network/nw:network-types/nl:network-layer-topology" {
        }
        description
          "Contains network layer link attributes";
        container network-layer-link-attributes {
            description
                "Contains network layer link attributes";
            leaf link-name {
                type string;
                description
                    "Name of the network layer link.";
            }
            leaf link-type {
                type enumeration{
                    enum ethernet;
                    enum ip;
                    enum 3gpp-5g-pdu-session;
                    enum 3gpp-5g-qos-flow;
                    enum tcp;
                    enum udp;
                    enum qos-flow;
                    enum pdu-session;
                    enum generic;
                }
                description
                    "Type of network layer link.";
            }
            leaf _5qi {
                type uint8;
                when "../link-type='3gpp-5g-qos-flow'"{}
            }
            leaf gfbr {
                type uint8;
                when "../link-type='3gpp-5g-qos-flow'"{}
            }
            leaf mfbr {
                type uint8;
                when "../link-type='3gpp-5g-qos-flow'"{}
            }
            leaf pdb {
                type uint8;
                when "../link-type='3gpp-5g-qos-flow'"{}
            }
            leaf per {
                type uint8;
                when "../link-type='3gpp-5g-qos-flow'"{}
            }
        }
    }
}
